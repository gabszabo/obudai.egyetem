module box {
  namespace "http://cisco.com/ns/examples/box";
  prefix box;

  import ietf-inet-types {
    prefix inet;
  }

  typedef if-speed-t {
    type enumeration {
      enum s10;
      enum s100;
      enum s1000;
      enum auto;
    }
  }

  container box {
    leaf hostname {
      type string;
    }

    container interfaces {
      list interface {
        key ifname;
        leaf ifname {
          type string {
            pattern "eth[0-9]+/[0-9]+";
          }
        }
        leaf ip {
          type inet:ipv4-prefix;
        }
        leaf link-state {
          config false;
          type enumeration {
            enum up;
            enum down;
          }
        }
        leaf if-speed {
          type if-speed-t;
        }
        leaf if-speed-current {
          type if-speed-t;
        }

      }
    }
  }
}
